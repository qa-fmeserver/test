FME workspace austinApartments.fmw
Title: City of Austin: Apartments and other (SPATIALITE 2 KML)

Parameters:
- SourceDataset_SPATIALITE_NATIVE = $(FME_MF_DIR_USERTYPED)\Landmarks.sqlite   # SpatiaLite Database

Readers:
- SPATIALITE_NATIVE_1: SPATIALITE_NATIVE from $(SourceDataset_SPATIALITE_NATIVE) in LL84

Writers:
- OGCKML_1: OGCKML to /opt/fmeserver//resources/system/temp/engineresults\austinApartments.kml in LL84

Note: Landmarks in Austin, in LL84
Landmarks (reader SPATIALITE_NATIVE_1)
    attributes: CFCC varchar(4), FILE integer, LALAT integer, LALONG integer, LANAME varchar(31), LAND integer, MODULE varchar(9), OBJECTID integer, SOURCE varchar(2)
    -> TestFilter
Note: Copy LANAME to kml_name / (legend entry and label)
AttributeCopier_kml_name
    ATTR_TABLE = COPY LANAME > kml_name
    MISSING_INPUT_ATTRS = PRESERVE
    -> Landmarks (writer OGCKML_1)
Landmarks (writer OGCKML_1)
    attributes: CFCC kml_char(4), FILE kml_char(20), LALAT kml_char(20), LALONG kml_char(20), LANAME kml_char(31), LAND kml_char(20), MODULE kml_char(9), OBJECTID kml_char(20), SOURCE kml_char(2)

Bookmark: Find landmark type
TestFilter
    DEFAULT_VALUE = <UNFILTERED>
    TEST_LIST:
      "BOOL_OP,OR,COMPOSITE_TEST,""""""1 OR 2"""""",TEST_CLAUSE,TEST @Value(LANAME) CONTAINS apartment
      TEST @Value(LANAME) CONTAINS townhome",Apartments,"BOOL_OP,OR,COMPOSITE_TEST,""""""1"""""",TEST_CLAUSE,TEST @Value(LANAME) CONTAINS school",School,"BOOL_OP,OR,COMPOSITE_TEST,""""""1 OR 2"""""",TEST_CLAUSE,TEST @Value(LANAME) CONTAINS shop
      TEST @Value(LANAME) CONTAINS mall",Shopping,"BOOL_OP,OR,COMPOSITE_TEST,""""""1 OR 2"""""",TEST_CLAUSE,TEST @Value(LANAME) CONTAINS airport
      TEST @Value(LANAME) CONTAINS international",Airports
    Apartments -> AttributeCreator_Apartments
    School -> AttributeCreator_School
    Shopping -> AttributeCreator_Shopping
    Airports -> AttributeCreator_Airports

Bookmark: Category for fanout
Note: Create the category attribute for / feature type fanout.
AttributeCreator_Apartments
    ATTR_TABLE = SET_TO category = Apartments
    -> KMLStyler_apartments
AttributeCreator_School
    ATTR_TABLE = SET_TO category = School
    -> KMLStyler_school
AttributeCreator_Shopping
    ATTR_TABLE = SET_TO category = Shopping
    -> KMLStyler_shopping
AttributeCreator_Airports
    ATTR_TABLE = SET_TO category = Airports
    -> KMLStyler_airports

Bookmark: Apply KML Style
KMLStyler_apartments
    FILL_OPACITY = 0.4
    ICON_NAME = I1
    ICON_OPACITY = 1.0
    ICON_SCALE = 0.7
    LABEL_OPACITY = 1.0
    LABEL_SCALE = 0.8
    LABEL_VISIBILITY = Yes
    LINE_WIDTH = 1.0
    LINE_WIDTH_UNITS = Pixels (Display Units)
    OPACITY = 1.0
    STYLE_PER_FEATURE = Yes
    KMLStyled -> AttributeCopier_kml_name
KMLStyler_school
    FILL_OPACITY = 0.4
    ICON_NAME = B2
    ICON_OPACITY = 1.0
    ICON_SCALE = 0.3
    LABEL_OPACITY = 1.0
    LABEL_SCALE = 0.6
    LABEL_VISIBILITY = Yes
    LINE_WIDTH = 1.0
    LINE_WIDTH_UNITS = Pixels (Display Units)
    OPACITY = 1.0
    STYLE_PER_FEATURE = Yes
    KMLStyled -> AttributeCopier_kml_name
KMLStyler_shopping
    FILL_OPACITY = 0.4
    ICON_NAME = D2
    ICON_OPACITY = 1.0
    ICON_SCALE = 0.3
    LABEL_OPACITY = 1.0
    LABEL_SCALE = 0.6
    LABEL_VISIBILITY = Yes
    LINE_WIDTH = 1.0
    LINE_WIDTH_UNITS = Pixels (Display Units)
    OPACITY = 1.0
    STYLE_PER_FEATURE = Yes
    KMLStyled -> AttributeCopier_kml_name
KMLStyler_airports
    FILL_OPACITY = 0.4
    ICON_NAME = M4
    ICON_OPACITY = 1.0
    ICON_SCALE = 0.6
    LABEL_OPACITY = 1.0
    LABEL_SCALE = 0.6
    LABEL_VISIBILITY = Yes
    LINE_WIDTH = 1.0
    LINE_WIDTH_UNITS = Pixels (Display Units)
    OPACITY = 1.0
    STYLE_PER_FEATURE = Yes
    KMLStyled -> AttributeCopier_kml_name
